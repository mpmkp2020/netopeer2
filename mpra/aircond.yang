module aircond {
    namespace "urn:aircond";
    prefix ov;

    revision 2018-01-19 {
        description "Initial revision.";
    }

    typedef aircond-temperature {
        description "Temperature range that is accepted by the aircond.";
        type uint8 {
            range "18..27";
        }
    }

    container aircond-state {
        description "State data container of the aircond.";

        leaf temperature {
            description "Actual temperature inside the aircond.";
            type aircond-temperature;
            default 22;
        }
    }

    rpc change-temperature {
        description "Operation to order the aircond to put the prepared food inside.";

        input {
            leaf xpath {
                description "Parameter determining when to perform the operation.";
                type string;
            }
            leaf datastore {
                type string;
                default "running";
            }
            leaf request {
                type enumeration {
                    enum SET {
                        description
                            "Set the temperature of AC";
                    }
                }
                default SET;
            }
            leaf value {
                type uint8 {
                    range "18..27";
                }
                default 22;
            }
        }
        output {
            leaf msg {
                type string;
            }
            leaf ret {
                type string;
            }
        }
    }

    rpc show-temperature {
        description "Operation to order the aircond to put the prepared food inside.";

        input {
            leaf xpath {
                description "Parameter determining when to perform the operation.";
                type string;
            }
            leaf datastore {
                type string;
                default "running";
            }
            leaf request {
                type enumeration {
                    enum GET {
                        description "Get the demperature of AC";
                    }
                }
                default GET;
            }
        }
        output {
            leaf msg {
                type string;
            }
            leaf ret {
                type string;
            }
        }
    }
}
